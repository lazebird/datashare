--
-- SCODENO.my
-- MIB generated by MG-SOFT Visual MIB Builder Version 6.0  Build 88
-- Friday, May 14, 2021 at 09:49:21
--

	SCODENO DEFINITIONS ::= BEGIN
 
		IMPORTS
			enterprises, MODULE-IDENTITY, OBJECT-IDENTITY			
				FROM SNMPv2-SMI;
	
	
		-- 1.3.6.1.4.1.51135.1.1
		scodenoGlobalModule MODULE-IDENTITY 
			LAST-UPDATED "202010151939Z"		-- October 15, 2020 at 19:39 GMT
			ORGANIZATION 
				"Scodeno"
			CONTACT-INFO 
				"lqy&dockeer.com.cn"
			DESCRIPTION 
				"Define all enterprise's private MIB nodes for NMS."
			REVISION "202010161142Z"		-- October 16, 2020 at 11:42 GMT
			DESCRIPTION 
				"init"
			::= { scodenoModule 1 }

		
	
--
-- Node definitions
--
	
		-- 1.3.6.1.4.1.51135
		scodeno OBJECT-IDENTITY
			STATUS current
			DESCRIPTION 
				"The root of the OID sub-tree assigned to Company by the Internet Assigned Numbers Authority (IANA)"
			::= { enterprises 51135 }

		
		-- 1.3.6.1.4.1.51135.1
		scodenoModule OBJECT IDENTIFIER ::= { scodeno 1 }

		
		-- 1.3.6.1.4.1.51135.2
		scodenoGeneric OBJECT-IDENTITY
			STATUS current
			DESCRIPTION 
				"Sub-tree for common object and event definitions"
			::= { scodeno 2 }

		
		-- 1.3.6.1.4.1.51135.3
		scodenoProducts OBJECT-IDENTITY
			STATUS current
			DESCRIPTION 
				"Sub-tree for specific object and event definitions"
			::= { scodeno 3 }

		
		-- 1.3.6.1.4.1.51135.4
		scodenoCaps OBJECT-IDENTITY
			STATUS current
			DESCRIPTION 
				"Sub-tree for agent profiles"
			::= { scodeno 4 }

		
		-- 1.3.6.1.4.1.51135.5
		scodenoReqs OBJECT-IDENTITY
			STATUS current
			DESCRIPTION 
				"Sub-tree for management application requirements"
			::= { scodeno 5 }

		
	
	END

--
-- SCODENO.my
--
