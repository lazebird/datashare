--
-- DKSYS-MIB.my
-- MIB generated by MG-SOFT Visual MIB Builder Version 6.0  Build 88
-- Friday, May 14, 2021 at 10:08:33
--

	DKSYS-MIB DEFINITIONS ::= BEGIN
 
		IMPORTS
			scodenoModule			
				FROM SCODENO			
			OBJECT-GROUP			
				FROM SNMPv2-CONF			
			OBJECT-TYPE, MODULE-IDENTITY			
				FROM SNMPv2-SMI;
	
	
		-- 1.3.6.1.4.1.51135.1.4.1
		dksysModule MODULE-IDENTITY 
			LAST-UPDATED "202010151939Z"		-- October 15, 2020 at 19:39 GMT
			ORGANIZATION 
				"Scodeno"
			CONTACT-INFO 
				"lqy@dockeer.com.cn"
			DESCRIPTION 
				"Define dksys private MIB nodes for NMS."
			REVISION "202010161142Z"		-- October 16, 2020 at 11:42 GMT
			DESCRIPTION 
				"init"
			::= { dksys 1 }

		
	
--
-- Node definitions
--
	
		-- 1.3.6.1.4.1.51135.1.4
		dksys OBJECT IDENTIFIER ::= { scodenoModule 4 }

		
		-- 1.3.6.1.4.1.51135.1.4.2
		operations OBJECT IDENTIFIER ::= { dksys 2 }

		
		-- 1.3.6.1.4.1.51135.1.4.2.1
		configurationOper OBJECT-TYPE
			SYNTAX INTEGER
				{
				save(1),
				empty(2),
				default(3)
				}
			MAX-ACCESS read-write
			STATUS current
			DESCRIPTION
				"Device's configuration operations."
			::= { operations 1 }

		
		-- 1.3.6.1.4.1.51135.1.4.2.2
		powerOper OBJECT-TYPE
			SYNTAX INTEGER
				{
				on(1),
				off(2),
				reset(3)
				}
			MAX-ACCESS read-write
			STATUS current
			DESCRIPTION
				"Device's power operations."
			::= { operations 2 }

		
		-- 1.3.6.1.4.1.51135.1.4.8
		dksysGroups OBJECT IDENTIFIER ::= { dksys 8 }

		
		-- 1.3.6.1.4.1.51135.1.4.8.1
		dksysTableGroup OBJECT-GROUP
			OBJECTS { configurationOper, powerOper }
			STATUS current
			DESCRIPTION 
				"Table & scalar nodes group."
			::= { dksysGroups 1 }

		
	
	END

--
-- DKSYS-MIB.my
--
