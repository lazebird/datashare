--
-- DOCKEER.my
-- MIB generated by MG-SOFT Visual MIB Builder Version 6.0  Build 88
-- Friday, May 14, 2021 at 10:09:33
--

	DOCKEER DEFINITIONS ::= BEGIN
 
		IMPORTS
			enterprises, MODULE-IDENTITY, OBJECT-IDENTITY			
				FROM SNMPv2-SMI;
	
	
		-- 1.3.6.1.4.1.57430.1.1
		dockeerGlobalModule MODULE-IDENTITY 
			LAST-UPDATED "202105131943Z"		-- May 13, 2021 at 19:43 GMT
			ORGANIZATION 
				"Fuzhou Dockeer Technology Co., Ltd."
			CONTACT-INFO 
				"lqy&dockeer.com.cn"
			DESCRIPTION 
				"All enterprise's private MIB nodes for NMS."
			REVISION "202105140947Z"		-- May 14, 2021 at 09:47 GMT
			DESCRIPTION 
				"init"
			::= { dockeerModule 1 }

		
	
--
-- Node definitions
--
	
		-- 1.3.6.1.4.1.57430
		dockeer OBJECT-IDENTITY
			STATUS current
			DESCRIPTION 
				"The root of the OID sub-tree assigned to Company by the Internet Assigned Numbers Authority (IANA)"
			::= { enterprises 57430 }

		
		-- 1.3.6.1.4.1.57430.1
		dockeerModule OBJECT IDENTIFIER ::= { dockeer 1 }

		
		-- 1.3.6.1.4.1.57430.2
		dockeerGeneric OBJECT-IDENTITY
			STATUS current
			DESCRIPTION 
				"Sub-tree for common object and event definitions"
			::= { dockeer 2 }

		
		-- 1.3.6.1.4.1.57430.3
		dockeerProducts OBJECT-IDENTITY
			STATUS current
			DESCRIPTION 
				"Sub-tree for specific object and event definitions"
			::= { dockeer 3 }

		
		-- 1.3.6.1.4.1.57430.4
		dockeerCaps OBJECT-IDENTITY
			STATUS current
			DESCRIPTION 
				"Sub-tree for agent profiles"
			::= { dockeer 4 }

		
		-- 1.3.6.1.4.1.57430.5
		dockeerReqs OBJECT-IDENTITY
			STATUS current
			DESCRIPTION 
				"Sub-tree for management application requirements"
			::= { dockeer 5 }

		
		-- 1.3.6.1.4.1.57430.6
		dockeerExpr OBJECT-IDENTITY
			STATUS current
			DESCRIPTION 
				"Sub-tree for experimental definitions"
			::= { dockeer 6 }

		
	
	END

--
-- DOCKEER.my
--
