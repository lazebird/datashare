--
-- DK-IOCTL-MIB.my
-- MIB generated by MG-SOFT Visual MIB Builder Version 6.0  Build 88
-- Monday, May 24, 2021 at 17:36:10
--

	DK-IOCTL-MIB DEFINITIONS ::= BEGIN
 
		IMPORTS
			dockeerModule			
				FROM DOCKEER			
			OBJECT-GROUP			
				FROM SNMPv2-CONF			
			Gauge32, OBJECT-TYPE, MODULE-IDENTITY			
				FROM SNMPv2-SMI;
	
	
		-- 1.3.6.1.4.1.57430.1.4.1
		ioctlModule MODULE-IDENTITY 
			LAST-UPDATED "202105101939Z"		-- May 10, 2021 at 19:39 GMT
			ORGANIZATION 
				"Fuzhou Dockeer Technology Co., Ltd."
			CONTACT-INFO 
				"lqy@dockeer.com.cn"
			DESCRIPTION 
				"Define ioctl private MIB nodes for NMS."
			REVISION "202010161142Z"		-- October 16, 2020 at 11:42 GMT
			DESCRIPTION 
				"init"
			::= { ioctl 1 }

		
	
--
-- Node definitions
--
	
		-- 1.3.6.1.4.1.57430.1.4
		ioctl OBJECT IDENTIFIER ::= { dockeerModule 4 }

		
		-- 1.3.6.1.4.1.57430.1.4.2
		ioctlTraps OBJECT IDENTIFIER ::= { ioctl 2 }

		
		-- 1.3.6.1.4.1.57430.1.4.3
		ioctlconfTable OBJECT-TYPE
			SYNTAX SEQUENCE OF IoctlconfEntry
			MAX-ACCESS not-accessible
			STATUS current
			DESCRIPTION
				"Ioctl module configuration table."
			::= { ioctl 3 }

		
		-- 1.3.6.1.4.1.57430.1.4.3.1
		ioctlconfEntry OBJECT-TYPE
			SYNTAX IoctlconfEntry
			MAX-ACCESS not-accessible
			STATUS current
			DESCRIPTION
				"Ioctl module configuration table entry."
			INDEX { confid }
			::= { ioctlconfTable 1 }

		
		IoctlconfEntry ::=
			SEQUENCE { 
				confid
					Gauge32,
				confdirection
					INTEGER,
				conflevel
					INTEGER,
				confdescription
					OCTET STRING,
				confRowStatus
					INTEGER
			 }

		-- 1.3.6.1.4.1.57430.1.4.3.1.1
		confid OBJECT-TYPE
			SYNTAX Gauge32 (1..255)
			MAX-ACCESS not-accessible
			STATUS current
			DESCRIPTION
				"Ioctl configuration id."
			::= { ioctlconfEntry 1 }

		
		-- 1.3.6.1.4.1.57430.1.4.3.1.2
		confdirection OBJECT-TYPE
			SYNTAX INTEGER
				{
				input(1),
				output(2)
				}
			MAX-ACCESS read-create
			STATUS current
			DESCRIPTION
				"Ioctl configuration direction."
			::= { ioctlconfEntry 2 }

		
		-- 1.3.6.1.4.1.57430.1.4.3.1.3
		conflevel OBJECT-TYPE
			SYNTAX INTEGER
				{
				low(1),
				high(2)
				}
			MAX-ACCESS read-create
			STATUS current
			DESCRIPTION
				"Ioctl configuration level."
			::= { ioctlconfEntry 3 }

		
		-- 1.3.6.1.4.1.57430.1.4.3.1.4
		confdescription OBJECT-TYPE
			SYNTAX OCTET STRING
			MAX-ACCESS read-create
			STATUS current
			DESCRIPTION
				"Ioctl configuration description."
			::= { ioctlconfEntry 4 }

		
		-- 1.3.6.1.4.1.57430.1.4.3.1.5
		confRowStatus OBJECT-TYPE
			SYNTAX INTEGER
				{
				active(1),
				notReady(3),
				createandWait(5),
				destroy(6)
				}
			MAX-ACCESS read-create
			STATUS current
			DESCRIPTION
				"Ioctl configuration rowstatus."
			::= { ioctlconfEntry 5 }

		
		-- 1.3.6.1.4.1.57430.1.4.8
		ioctlGroups OBJECT IDENTIFIER ::= { ioctl 8 }

		
		-- 1.3.6.1.4.1.57430.1.4.8.1
		ioctlTableGroup OBJECT-GROUP
			OBJECTS { confdirection, conflevel, confdescription, confRowStatus }
			STATUS current
			DESCRIPTION 
				"Table & scalar nodes group."
			::= { ioctlGroups 1 }

		
	
	END

--
-- DK-IOCTL-MIB.my
--
