--
-- DK-SYS-MIB.my
-- MIB generated by MG-SOFT Visual MIB Builder Version 6.0  Build 88
-- Monday, May 24, 2021 at 17:31:37
--

	DK-SYS-MIB DEFINITIONS ::= BEGIN
 
		IMPORTS
			dockeerModule			
				FROM DOCKEER			
			OBJECT-GROUP			
				FROM SNMPv2-CONF			
			OBJECT-TYPE, MODULE-IDENTITY			
				FROM SNMPv2-SMI;
	
	
		-- 1.3.6.1.4.1.57430.1.2.1
		sysModule MODULE-IDENTITY 
			LAST-UPDATED "202010151939Z"		-- October 15, 2020 at 19:39 GMT
			ORGANIZATION 
				"Fuzhou Dockeer Technology Co., Ltd."
			CONTACT-INFO 
				"lqy@dockeer.com.cn"
			DESCRIPTION 
				"Define system private MIB nodes for NMS."
			REVISION "202010161142Z"		-- October 16, 2020 at 11:42 GMT
			DESCRIPTION 
				"init"
			::= { sys 1 }

		
	
--
-- Node definitions
--
	
		-- 1.3.6.1.4.1.57430.1.2
		sys OBJECT IDENTIFIER ::= { dockeerModule 2 }

		
		-- 1.3.6.1.4.1.57430.1.2.2
		operations OBJECT IDENTIFIER ::= { sys 2 }

		
		-- 1.3.6.1.4.1.57430.1.2.2.1
		configurationOper OBJECT-TYPE
			SYNTAX INTEGER
				{
				save(1),
				empty(2),
				default(3)
				}
			MAX-ACCESS read-write
			STATUS current
			DESCRIPTION
				"Device's configuration operations."
			::= { operations 1 }

		
		-- 1.3.6.1.4.1.57430.1.2.2.2
		powerOper OBJECT-TYPE
			SYNTAX INTEGER
				{
				on(1),
				off(2),
				reset(3)
				}
			MAX-ACCESS read-write
			STATUS current
			DESCRIPTION
				"Device's power operations."
			::= { operations 2 }

		
		-- 1.3.6.1.4.1.57430.1.2.8
		sysGroups OBJECT IDENTIFIER ::= { sys 8 }

		
		-- 1.3.6.1.4.1.57430.1.2.8.1
		sysTableGroup OBJECT-GROUP
			OBJECTS { configurationOper, powerOper }
			STATUS current
			DESCRIPTION 
				"Table & scalar nodes group."
			::= { sysGroups 1 }

		
	
	END

--
-- DK-SYS-MIB.my
--
