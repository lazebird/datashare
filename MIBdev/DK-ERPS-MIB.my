--
-- DK-ERPS-MIB.my
-- MIB generated by MG-SOFT Visual MIB Builder Version 6.0  Build 88
-- Monday, May 24, 2021 at 18:51:28
--

	DK-ERPS-MIB DEFINITIONS ::= BEGIN
 
		IMPORTS
			dockeerModule			
				FROM DOCKEER			
			OBJECT-GROUP, NOTIFICATION-GROUP			
				FROM SNMPv2-CONF			
			Opaque, Gauge32, OBJECT-TYPE, MODULE-IDENTITY, NOTIFICATION-TYPE			
				FROM SNMPv2-SMI;
	
	
		-- 1.3.6.1.4.1.57430.1.3.1
		erpsModule MODULE-IDENTITY 
			LAST-UPDATED "202010171042Z"		-- October 17, 2020 at 10:42 GMT
			ORGANIZATION 
				"Fuzhou Dockeer Technology Co., Ltd."
			CONTACT-INFO 
				"lqy@dockeer.com.cn"
			DESCRIPTION 
				"Define ERPS module MIBs & Traps."
			REVISION "202010171043Z"		-- October 17, 2020 at 10:43 GMT
			DESCRIPTION 
				"init"
			::= { erps 1 }

		
	
--
-- Node definitions
--
	
--  1.3.6.1.4.1.51135.1.3
		-- 1.3.6.1.4.1.57430.1.3
		erps OBJECT IDENTIFIER ::= { dockeerModule 3 }

		
-- 1.3.6.1.4.1.51135.1.2.2
		-- 1.3.6.1.4.1.57430.1.3.2
		erpsTraps OBJECT IDENTIFIER ::= { erps 2 }

		
		-- 1.3.6.1.4.1.57430.1.3.2.1
		linkStatechange NOTIFICATION-TYPE
			OBJECTS { erpsStateInstName, eastLinkState, westLinkState, lastPriority }
			STATUS current
			DESCRIPTION 
				"ERPS instance link change event."
			::= { erpsTraps 1 }

		
		-- 1.3.6.1.4.1.57430.1.3.2.2
		instStatechange NOTIFICATION-TYPE
			OBJECTS { erpsStateInstName, instState, lastPriority }
			STATUS current
			DESCRIPTION 
				"ERPS instance state change event."
			::= { erpsTraps 2 }

		
-- 1.3.6.1.4.1.51135.1.2.3
		-- 1.3.6.1.4.1.57430.1.3.3
		erpsRingTable OBJECT-TYPE
			SYNTAX SEQUENCE OF ErpsRingEntry
			MAX-ACCESS not-accessible
			STATUS current
			DESCRIPTION
				"ERPS ring configuration table."
			::= { erps 3 }

		
		-- 1.3.6.1.4.1.57430.1.3.3.1
		erpsRingEntry OBJECT-TYPE
			SYNTAX ErpsRingEntry
			MAX-ACCESS not-accessible
			STATUS current
			DESCRIPTION
				"ERPS ring configuration table entry."
			INDEX { index }
			::= { erpsRingTable 1 }

		
		ErpsRingEntry ::=
			SEQUENCE { 
				index
					Gauge32,
				eastInterface
					OCTET STRING,
				westInterface
					OCTET STRING,
				ringRowStatus
					INTEGER
			 }

		-- 1.3.6.1.4.1.57430.1.3.3.1.1
		index OBJECT-TYPE
			SYNTAX Gauge32 (1..255)
			MAX-ACCESS not-accessible
			STATUS current
			DESCRIPTION
				"ERPS ring index."
			::= { erpsRingEntry 1 }

		
		-- 1.3.6.1.4.1.57430.1.3.3.1.2
		eastInterface OBJECT-TYPE
			SYNTAX OCTET STRING (SIZE (1..32))
			MAX-ACCESS read-create
			STATUS current
			DESCRIPTION
				"East interface name."
			::= { erpsRingEntry 2 }

		
		-- 1.3.6.1.4.1.57430.1.3.3.1.3
		westInterface OBJECT-TYPE
			SYNTAX OCTET STRING (SIZE (1..32))
			MAX-ACCESS read-create
			STATUS current
			DESCRIPTION
				"West interface name."
			::= { erpsRingEntry 3 }

		
		-- 1.3.6.1.4.1.57430.1.3.3.1.4
		ringRowStatus OBJECT-TYPE
			SYNTAX INTEGER
				{
				active(1),
				notReady(3),
				createandWait(5),
				destroy(6)
				}
			MAX-ACCESS read-create
			STATUS current
			DESCRIPTION
				"Ring row status."
			::= { erpsRingEntry 4 }

		
-- 1.3.6.1.4.1.51135.1.2.4
		-- 1.3.6.1.4.1.57430.1.3.4
		erpsProfTable OBJECT-TYPE
			SYNTAX SEQUENCE OF ErpsProfEntry
			MAX-ACCESS not-accessible
			STATUS current
			DESCRIPTION
				"ERPS profile configuration table."
			::= { erps 4 }

		
		-- 1.3.6.1.4.1.57430.1.3.4.1
		erpsProfEntry OBJECT-TYPE
			SYNTAX ErpsProfEntry
			MAX-ACCESS not-accessible
			STATUS current
			DESCRIPTION
				"ERPS profile configuration table entry."
			INDEX { profName }
			::= { erpsProfTable 1 }

		
		ErpsProfEntry ::=
			SEQUENCE { 
				profName
					OCTET STRING,
				wtrTimerVal
					Gauge32,
				wtbTimerVal
					Gauge32,
				guardTimerVal
					Gauge32,
				holdoffTimerVal
					Gauge32,
				revertive
					INTEGER,
				profRowStatus
					INTEGER
			 }

		-- 1.3.6.1.4.1.57430.1.3.4.1.1
		profName OBJECT-TYPE
			SYNTAX OCTET STRING (SIZE (1..32))
			MAX-ACCESS not-accessible
			STATUS current
			DESCRIPTION
				"Profile name."
			::= { erpsProfEntry 1 }

		
		-- 1.3.6.1.4.1.57430.1.3.4.1.2
		wtrTimerVal OBJECT-TYPE
			SYNTAX Gauge32 (1..12)
			UNITS "minute"
			MAX-ACCESS read-create
			STATUS current
			DESCRIPTION
				"Wait to restore timer value.Units: minute."
			DEFVAL { 5 }
			::= { erpsProfEntry 2 }

		
		-- 1.3.6.1.4.1.57430.1.3.4.1.3
		wtbTimerVal OBJECT-TYPE
			SYNTAX Gauge32 (60..720)
			UNITS "millisecond"
			MAX-ACCESS read-only
			STATUS current
			DESCRIPTION
				"Wait to block timer value.Units: millisecond."
			::= { erpsProfEntry 3 }

		
		-- 1.3.6.1.4.1.57430.1.3.4.1.4
		guardTimerVal OBJECT-TYPE
			SYNTAX Gauge32 (10..2000)
			UNITS "millisecond"
			MAX-ACCESS read-create
			STATUS current
			DESCRIPTION
				"Guard timer value.Units: millisecond."
			DEFVAL { 500 }
			::= { erpsProfEntry 4 }

		
		-- 1.3.6.1.4.1.57430.1.3.4.1.5
		holdoffTimerVal OBJECT-TYPE
			SYNTAX Gauge32 (0..100)
			UNITS "100 milliseconds"
			MAX-ACCESS read-create
			STATUS current
			DESCRIPTION
				"Hold off timer value.Units: 100 milliseconds."
			DEFVAL { 0 }
			::= { erpsProfEntry 5 }

		
		-- 1.3.6.1.4.1.57430.1.3.4.1.6
		revertive OBJECT-TYPE
			SYNTAX INTEGER
				{
				true(1),
				false(2)
				}
			MAX-ACCESS read-create
			STATUS current
			DESCRIPTION
				"Revertive mode."
			DEFVAL { 1 }
			::= { erpsProfEntry 6 }

		
		-- 1.3.6.1.4.1.57430.1.3.4.1.7
		profRowStatus OBJECT-TYPE
			SYNTAX INTEGER
				{
				active(1),
				notReady(3),
				createandWait(5),
				destroy(6)
				}
			MAX-ACCESS read-create
			STATUS current
			DESCRIPTION
				"Profile row status."
			::= { erpsProfEntry 7 }

		
-- 1.3.6.1.4.1.51135.1.2.5
		-- 1.3.6.1.4.1.57430.1.3.5
		erpsInstTable OBJECT-TYPE
			SYNTAX SEQUENCE OF ErpsInstEntry
			MAX-ACCESS not-accessible
			STATUS current
			DESCRIPTION
				"ERPS instance configuration table."
			::= { erps 5 }

		
		-- 1.3.6.1.4.1.57430.1.3.5.1
		erpsInstEntry OBJECT-TYPE
			SYNTAX ErpsInstEntry
			MAX-ACCESS not-accessible
			STATUS current
			DESCRIPTION
				"ERPS instance configuration table entry."
			INDEX { instName }
			::= { erpsInstTable 1 }

		
		ErpsInstEntry ::=
			SEQUENCE { 
				instName
					OCTET STRING,
				ring
					Gauge32,
				instance
					Gauge32,
				profile
					OCTET STRING,
				groupRole
					INTEGER,
				groupPeer
					OCTET STRING,
				level
					Gauge32,
				rapsVid
					Gauge32,
				rplRole
					INTEGER,
				rplInterface
					INTEGER,
				subRingChannel
					INTEGER,
				subRingIf
					INTEGER,
				attachedInst
					OCTET STRING,
				instRowStatus
					INTEGER
			 }

		-- 1.3.6.1.4.1.57430.1.3.5.1.1
		instName OBJECT-TYPE
			SYNTAX OCTET STRING (SIZE (1..32))
			MAX-ACCESS not-accessible
			STATUS current
			DESCRIPTION
				"Instance name."
			::= { erpsInstEntry 1 }

		
		-- 1.3.6.1.4.1.57430.1.3.5.1.2
		ring OBJECT-TYPE
			SYNTAX Gauge32 (1..255)
			MAX-ACCESS read-create
			STATUS current
			DESCRIPTION
				"Associated ring index."
			::= { erpsInstEntry 2 }

		
		-- 1.3.6.1.4.1.57430.1.3.5.1.3
		instance OBJECT-TYPE
			SYNTAX Gauge32 (0..4096)
			MAX-ACCESS read-create
			STATUS current
			DESCRIPTION
				"Instance id for hardware."
			DEFVAL { 0 }
			::= { erpsInstEntry 3 }

		
		-- 1.3.6.1.4.1.57430.1.3.5.1.4
		profile OBJECT-TYPE
			SYNTAX OCTET STRING (SIZE (0..32))
			MAX-ACCESS read-create
			STATUS current
			DESCRIPTION
				"Associated profile name."
			DEFVAL { "Default" }
			::= { erpsInstEntry 4 }

		
		-- 1.3.6.1.4.1.57430.1.3.5.1.5
		groupRole OBJECT-TYPE
			SYNTAX INTEGER
				{
				none(0),
				master(1),
				backup(2)
				}
			MAX-ACCESS read-create
			STATUS current
			DESCRIPTION
				"Group role, used in backup ring solution."
			DEFVAL { 0 }
			::= { erpsInstEntry 5 }

		
		-- 1.3.6.1.4.1.57430.1.3.5.1.6
		groupPeer OBJECT-TYPE
			SYNTAX OCTET STRING (SIZE (0..32))
			MAX-ACCESS read-create
			STATUS current
			DESCRIPTION
				"Group peer instance name, used in backup ring solution."
			DEFVAL { "" }
			::= { erpsInstEntry 6 }

		
		-- 1.3.6.1.4.1.57430.1.3.5.1.7
		level OBJECT-TYPE
			SYNTAX Gauge32 (0..7)
			MAX-ACCESS read-create
			STATUS current
			DESCRIPTION
				"CFM packet level/mel."
			DEFVAL { 0 }
			::= { erpsInstEntry 7 }

		
		-- 1.3.6.1.4.1.57430.1.3.5.1.8
		rapsVid OBJECT-TYPE
			SYNTAX Gauge32 (1..4096)
			MAX-ACCESS read-create
			STATUS current
			DESCRIPTION
				"Vlan id used by raps packet."
			DEFVAL { 1000 }
			::= { erpsInstEntry 8 }

		
		-- 1.3.6.1.4.1.57430.1.3.5.1.9
		rplRole OBJECT-TYPE
			SYNTAX INTEGER
				{
				none(0),
				owner(1),
				neighbor(2),
				nextNeighbor(3)
				}
			MAX-ACCESS read-create
			STATUS current
			DESCRIPTION
				"Rpl role."
			DEFVAL { 0 }
			::= { erpsInstEntry 9 }

		
		-- 1.3.6.1.4.1.57430.1.3.5.1.10
		rplInterface OBJECT-TYPE
			SYNTAX INTEGER
				{
				none(0),
				east(1),
				west(2)
				}
			MAX-ACCESS read-create
			STATUS current
			DESCRIPTION
				"Rpl role associated interface."
			DEFVAL { 0 }
			::= { erpsInstEntry 10 }

		
		-- 1.3.6.1.4.1.57430.1.3.5.1.11
		subRingChannel OBJECT-TYPE
			SYNTAX INTEGER
				{
				none(0),
				virtual(1),
				nonVirtual(2)
				}
			MAX-ACCESS read-create
			STATUS current
			DESCRIPTION
				"Subring channel mode."
			DEFVAL { 0 }
			::= { erpsInstEntry 11 }

		
		-- 1.3.6.1.4.1.57430.1.3.5.1.12
		subRingIf OBJECT-TYPE
			SYNTAX INTEGER
				{
				none(0),
				east(1),
				west(2)
				}
			MAX-ACCESS read-create
			STATUS current
			DESCRIPTION
				"Interface shared with subring."
			DEFVAL { 0 }
			::= { erpsInstEntry 12 }

		
		-- 1.3.6.1.4.1.57430.1.3.5.1.13
		attachedInst OBJECT-TYPE
			SYNTAX OCTET STRING (SIZE (0..32))
			MAX-ACCESS read-create
			STATUS current
			DESCRIPTION
				"Attached major instance name."
			DEFVAL { "" }
			::= { erpsInstEntry 13 }

		
		-- 1.3.6.1.4.1.57430.1.3.5.1.14
		instRowStatus OBJECT-TYPE
			SYNTAX INTEGER
				{
				active(1),
				notReady(3),
				createandWait(5),
				destroy(6)
				}
			MAX-ACCESS read-create
			STATUS current
			DESCRIPTION
				"Instance row status."
			::= { erpsInstEntry 14 }

		
-- 1.3.6.1.4.1.51135.1.2.6
		-- 1.3.6.1.4.1.57430.1.3.6
		erpsInstAdminTable OBJECT-TYPE
			SYNTAX SEQUENCE OF ErpsInstAdminEntry
			MAX-ACCESS not-accessible
			STATUS current
			DESCRIPTION
				"ERPS instance admin table."
			::= { erps 6 }

		
		-- 1.3.6.1.4.1.57430.1.3.6.1
		erpsInstAdminEntry OBJECT-TYPE
			SYNTAX ErpsInstAdminEntry
			MAX-ACCESS not-accessible
			STATUS current
			DESCRIPTION
				"ERPS instance admin table entry."
			INDEX { instAdminName }
			::= { erpsInstAdminTable 1 }

		
		ErpsInstAdminEntry ::=
			SEQUENCE { 
				instAdminName
					OCTET STRING,
				adminCmd
					INTEGER,
				adminLink
					INTEGER,
				instAdminRowStatus
					INTEGER
			 }

		-- 1.3.6.1.4.1.57430.1.3.6.1.1
		instAdminName OBJECT-TYPE
			SYNTAX OCTET STRING (SIZE (1..32))
			MAX-ACCESS not-accessible
			STATUS current
			DESCRIPTION
				"Instance name."
			::= { erpsInstAdminEntry 1 }

		
		-- 1.3.6.1.4.1.57430.1.3.6.1.2
		adminCmd OBJECT-TYPE
			SYNTAX INTEGER
				{
				none(0),
				forceSwitch(1),
				manualSwitch(2),
				clear(3)
				}
			MAX-ACCESS read-write
			STATUS current
			DESCRIPTION
				"Admin command."
			::= { erpsInstAdminEntry 2 }

		
		-- 1.3.6.1.4.1.57430.1.3.6.1.3
		adminLink OBJECT-TYPE
			SYNTAX INTEGER
				{
				none(0),
				east(1),
				west(2)
				}
			MAX-ACCESS read-write
			STATUS current
			DESCRIPTION
				"Admin command target interface."
			::= { erpsInstAdminEntry 3 }

		
		-- 1.3.6.1.4.1.57430.1.3.6.1.4
		instAdminRowStatus OBJECT-TYPE
			SYNTAX INTEGER
				{
				active(1),
				notReady(3),
				createandWait(5),
				destroy(6)
				}
			MAX-ACCESS read-write
			STATUS current
			DESCRIPTION
				"Instance admin row status."
			::= { erpsInstAdminEntry 4 }

		
-- 1.3.6.1.4.1.51135.1.2.7
		-- 1.3.6.1.4.1.57430.1.3.7
		erpsStateTable OBJECT-TYPE
			SYNTAX SEQUENCE OF ErpsStateEntry
			MAX-ACCESS not-accessible
			STATUS current
			DESCRIPTION
				"ERPS instance state table."
			::= { erps 7 }

		
		-- 1.3.6.1.4.1.57430.1.3.7.1
		erpsStateEntry OBJECT-TYPE
			SYNTAX ErpsStateEntry
			MAX-ACCESS not-accessible
			STATUS current
			DESCRIPTION
				"ERPS instance state table entry."
			INDEX { erpsStateInstName }
			::= { erpsStateTable 1 }

		
		ErpsStateEntry ::=
			SEQUENCE { 
				erpsStateInstName
					OCTET STRING,
				erpsStateRing
					Gauge32,
				instState
					INTEGER,
				curGroupRole
					INTEGER,
				confGroupRole
					INTEGER,
				curRingSize
					Gauge32,
				maxRingSize
					Gauge32,
				lastPriority
					INTEGER,
				eastLinkStatus
					INTEGER,
				eastLinkState
					INTEGER,
				eastNodeid
					Opaque,
				eastBpr
					INTEGER,
				westLinkStatus
					INTEGER,
				westLinkState
					INTEGER,
				westNodeid
					Opaque,
				westBpr
					INTEGER
			 }

		-- 1.3.6.1.4.1.57430.1.3.7.1.1
		erpsStateInstName OBJECT-TYPE
			SYNTAX OCTET STRING (SIZE (1..32))
			MAX-ACCESS accessible-for-notify
			STATUS current
			DESCRIPTION
				"Instance name."
			::= { erpsStateEntry 1 }

		
		-- 1.3.6.1.4.1.57430.1.3.7.1.2
		erpsStateRing OBJECT-TYPE
			SYNTAX Gauge32 (1..255)
			MAX-ACCESS read-only
			STATUS current
			DESCRIPTION
				"Ring index."
			::= { erpsStateEntry 2 }

		
		-- 1.3.6.1.4.1.57430.1.3.7.1.3
		instState OBJECT-TYPE
			SYNTAX INTEGER
				{
				init(1),
				pending(2),
				idle(3),
				fs(4),
				protection(5),
				ms(6)
				}
			MAX-ACCESS read-only
			STATUS current
			DESCRIPTION
				"Instance state."
			::= { erpsStateEntry 3 }

		
		-- 1.3.6.1.4.1.57430.1.3.7.1.4
		curGroupRole OBJECT-TYPE
			SYNTAX INTEGER
				{
				none(0),
				master(1),
				backup(2)
				}
			MAX-ACCESS read-only
			STATUS current
			DESCRIPTION
				"Current group role."
			::= { erpsStateEntry 4 }

		
		-- 1.3.6.1.4.1.57430.1.3.7.1.5
		confGroupRole OBJECT-TYPE
			SYNTAX INTEGER
				{
				none(0),
				master(1),
				backup(2)
				}
			MAX-ACCESS read-only
			STATUS current
			DESCRIPTION
				"Configured group role."
			::= { erpsStateEntry 5 }

		
		-- 1.3.6.1.4.1.57430.1.3.7.1.6
		curRingSize OBJECT-TYPE
			SYNTAX Gauge32
			MAX-ACCESS read-only
			STATUS current
			DESCRIPTION
				"Current ring size."
			::= { erpsStateEntry 6 }

		
		-- 1.3.6.1.4.1.57430.1.3.7.1.7
		maxRingSize OBJECT-TYPE
			SYNTAX Gauge32
			MAX-ACCESS read-only
			STATUS current
			DESCRIPTION
				"Max ring size."
			::= { erpsStateEntry 7 }

		
		-- 1.3.6.1.4.1.57430.1.3.7.1.8
		lastPriority OBJECT-TYPE
			SYNTAX INTEGER
				{
				noReq(0),
				rapsNr(1),
				rapsNrRb(2),
				wtbRun(3),
				wtbexp(4),
				wtrRun(5),
				wtrExp(6),
				adminMs(7),
				rapsMs(8),
				rapsSf(9),
				localClearSf(10),
				localSf(11),
				rapsFs(12),
				adminFs(13),
				adminClear(14),
				initialize(15)
				}
			MAX-ACCESS read-only
			STATUS current
			DESCRIPTION
				"Last event priority."
			::= { erpsStateEntry 8 }

		
		-- 1.3.6.1.4.1.57430.1.3.7.1.9
		eastLinkStatus OBJECT-TYPE
			SYNTAX INTEGER
				{
				invalid(0),
				up(1),
				down(2)
				}
			MAX-ACCESS read-only
			STATUS current
			DESCRIPTION
				"East interface link status."
			::= { erpsStateEntry 9 }

		
		-- 1.3.6.1.4.1.57430.1.3.7.1.10
		eastLinkState OBJECT-TYPE
			SYNTAX INTEGER
				{
				invalid(0),
				unblocked(1),
				blocked(2)
				}
			MAX-ACCESS read-only
			STATUS current
			DESCRIPTION
				"East interface link state."
			::= { erpsStateEntry 10 }

		
		-- 1.3.6.1.4.1.57430.1.3.7.1.11
		eastNodeid OBJECT-TYPE
			SYNTAX Opaque (SIZE (6))
			MAX-ACCESS read-only
			STATUS current
			DESCRIPTION
				"East interface nodeid record."
			::= { erpsStateEntry 11 }

		
		-- 1.3.6.1.4.1.57430.1.3.7.1.12
		eastBpr OBJECT-TYPE
			SYNTAX INTEGER
				{
				true(1),
				false(2)
				}
			MAX-ACCESS read-only
			STATUS current
			DESCRIPTION
				"East interface bpr record."
			::= { erpsStateEntry 12 }

		
		-- 1.3.6.1.4.1.57430.1.3.7.1.13
		westLinkStatus OBJECT-TYPE
			SYNTAX INTEGER
				{
				invalid(0),
				up(1),
				down(2)
				}
			MAX-ACCESS read-only
			STATUS current
			DESCRIPTION
				"West interface link status."
			::= { erpsStateEntry 13 }

		
		-- 1.3.6.1.4.1.57430.1.3.7.1.14
		westLinkState OBJECT-TYPE
			SYNTAX INTEGER
				{
				invalid(0),
				unblocked(1),
				blocked(2)
				}
			MAX-ACCESS read-only
			STATUS current
			DESCRIPTION
				"West interface link state."
			::= { erpsStateEntry 14 }

		
		-- 1.3.6.1.4.1.57430.1.3.7.1.15
		westNodeid OBJECT-TYPE
			SYNTAX Opaque (SIZE (6))
			MAX-ACCESS read-only
			STATUS current
			DESCRIPTION
				"West interface nodeid record."
			::= { erpsStateEntry 15 }

		
		-- 1.3.6.1.4.1.57430.1.3.7.1.16
		westBpr OBJECT-TYPE
			SYNTAX INTEGER
				{
				true(1),
				false(2)
				}
			MAX-ACCESS read-only
			STATUS current
			DESCRIPTION
				"West interface bpr record."
			::= { erpsStateEntry 16 }

		
-- 1.3.6.1.4.1.51135.1.2.8
		-- 1.3.6.1.4.1.57430.1.3.8
		erpsgroups OBJECT IDENTIFIER ::= { erps 8 }

		
		-- 1.3.6.1.4.1.57430.1.3.8.1
		erpsTableGroup OBJECT-GROUP
			OBJECTS { eastInterface, westInterface, ringRowStatus, wtrTimerVal, wtbTimerVal, 
				guardTimerVal, holdoffTimerVal, revertive, profRowStatus, instance, 
				profile, groupRole, groupPeer, level, rapsVid, 
				rplRole, rplInterface, subRingChannel, subRingIf, attachedInst, 
				adminCmd, adminLink, instRowStatus, instState, curGroupRole, 
				confGroupRole, curRingSize, maxRingSize, lastPriority, eastLinkStatus, 
				eastLinkState, eastNodeid, eastBpr, westLinkStatus, westLinkState, 
				westNodeid, ring, erpsStateRing, instAdminRowStatus, westBpr, 
				erpsStateInstName }
			STATUS current
			DESCRIPTION 
				"ERPS table node group."
			::= { erpsgroups 1 }

		
		-- 1.3.6.1.4.1.57430.1.3.8.2
		erpsTrapGroup NOTIFICATION-GROUP
			NOTIFICATIONS { linkStatechange, instStatechange }
			STATUS current
			DESCRIPTION 
				"ERPS trap node group."
			::= { erpsgroups 2 }

		
	
	END

--
-- DK-ERPS-MIB.my
--
