--
-- DK-POE-MIB.my
-- MIB generated by MG-SOFT Visual MIB Builder Version 6.0  Build 88
-- Monday, May 24, 2021 at 11:33:25
--

	DK-POE-MIB DEFINITIONS ::= BEGIN
 
		IMPORTS
			dockeerModule			
				FROM DOCKEER			
			OBJECT-GROUP			
				FROM SNMPv2-CONF			
			Integer32, OBJECT-TYPE, MODULE-IDENTITY			
				FROM SNMPv2-SMI;
	
	
		-- 1.3.6.1.4.1.57430.1.5.1
		poeModule MODULE-IDENTITY 
			LAST-UPDATED "202105211943Z"		-- May 21, 2021 at 19:43 GMT
			ORGANIZATION 
				"Fuzhou Dockeer Technology Co., Ltd."
			CONTACT-INFO 
				"lqy&dockeer.com.cn"
			DESCRIPTION 
				"PoE module for NMS."
			REVISION "202105211854Z"		-- May 21, 2021 at 18:54 GMT
			DESCRIPTION 
				"init"
			::= { poe 1 }

		
	
--
-- Node definitions
--
	
		-- 1.3.6.1.4.1.57430.1.5
		poe OBJECT IDENTIFIER ::= { dockeerModule 5 }

		
		-- 1.3.6.1.4.1.57430.1.5.2
		poeTraps OBJECT IDENTIFIER ::= { poe 2 }

		
		-- 1.3.6.1.4.1.57430.1.5.3
		pseStateTable OBJECT-TYPE
			SYNTAX SEQUENCE OF PseStateEntry
			MAX-ACCESS not-accessible
			STATUS current
			DESCRIPTION
				"Pse state table nodes."
			::= { poe 3 }

		
		-- 1.3.6.1.4.1.57430.1.5.3.1
		pseStateEntry OBJECT-TYPE
			SYNTAX PseStateEntry
			MAX-ACCESS not-accessible
			STATUS current
			DESCRIPTION
				"Pse state table entry."
			INDEX { pseStateGroupIndex }
			::= { pseStateTable 1 }

		
		PseStateEntry ::=
			SEQUENCE { 
				pseStateGroupIndex
					Integer32,
				pseStatePowerConsume
					Integer32,
				pseStatePoweredPorts
					Integer32
			 }

		-- 1.3.6.1.4.1.57430.1.5.3.1.1
		pseStateGroupIndex OBJECT-TYPE
			SYNTAX Integer32 (1..2147483647)
			MAX-ACCESS not-accessible
			STATUS current
			DESCRIPTION
				"Pse group index."
			::= { pseStateEntry 1 }

		
		-- 1.3.6.1.4.1.57430.1.5.3.1.2
		pseStatePowerConsume OBJECT-TYPE
			SYNTAX Integer32
			MAX-ACCESS read-only
			STATUS current
			DESCRIPTION
				"Pse's power consumption, unit is 0.1 watt."
			::= { pseStateEntry 2 }

		
		-- 1.3.6.1.4.1.57430.1.5.3.1.3
		pseStatePoweredPorts OBJECT-TYPE
			SYNTAX Integer32
			MAX-ACCESS read-only
			STATUS current
			DESCRIPTION
				"Pse powered ports."
			::= { pseStateEntry 3 }

		
		-- 1.3.6.1.4.1.57430.1.5.4
		portStateTable OBJECT-TYPE
			SYNTAX SEQUENCE OF PortStateEntry
			MAX-ACCESS not-accessible
			STATUS current
			DESCRIPTION
				"Port state table nodes."
			::= { poe 4 }

		
		-- 1.3.6.1.4.1.57430.1.5.4.1
		portStateEntry OBJECT-TYPE
			SYNTAX PortStateEntry
			MAX-ACCESS not-accessible
			STATUS current
			DESCRIPTION
				"Port state table entry."
			INDEX { portStateGroupIndex, portStateIndex }
			::= { portStateTable 1 }

		
		PortStateEntry ::=
			SEQUENCE { 
				portStateGroupIndex
					Integer32,
				portStateIndex
					Integer32,
				portStateDesc
					OCTET STRING,
				portStateIcut
					Integer32,
				portStatePower
					Integer32
			 }

		-- 1.3.6.1.4.1.57430.1.5.4.1.1
		portStateGroupIndex OBJECT-TYPE
			SYNTAX Integer32 (1..2147483647)
			MAX-ACCESS not-accessible
			STATUS current
			DESCRIPTION
				"Pse group index."
			::= { portStateEntry 1 }

		
		-- 1.3.6.1.4.1.57430.1.5.4.1.2
		portStateIndex OBJECT-TYPE
			SYNTAX Integer32 (1..2147483647)
			MAX-ACCESS not-accessible
			STATUS current
			DESCRIPTION
				"Port index."
			::= { portStateEntry 2 }

		
		-- 1.3.6.1.4.1.57430.1.5.4.1.3
		portStateDesc OBJECT-TYPE
			SYNTAX OCTET STRING
			MAX-ACCESS read-only
			STATUS current
			DESCRIPTION
				"Port description."
			::= { portStateEntry 3 }

		
		-- 1.3.6.1.4.1.57430.1.5.4.1.4
		portStateIcut OBJECT-TYPE
			SYNTAX Integer32
			MAX-ACCESS read-only
			STATUS current
			DESCRIPTION
				"Port current icut, unit is 0.1 mA."
			::= { portStateEntry 4 }

		
		-- 1.3.6.1.4.1.57430.1.5.4.1.5
		portStatePower OBJECT-TYPE
			SYNTAX Integer32
			MAX-ACCESS read-only
			STATUS current
			DESCRIPTION
				"Port current power, unit is 0.1 watt."
			::= { portStateEntry 5 }

		
		-- 1.3.6.1.4.1.57430.1.5.10
		poeGroups OBJECT IDENTIFIER ::= { poe 10 }

		
		-- 1.3.6.1.4.1.57430.1.5.10.1
		poeTableGroup OBJECT-GROUP
			OBJECTS { pseStatePowerConsume, pseStatePoweredPorts, portStateDesc, portStateIcut, portStatePower
				 }
			STATUS current
			DESCRIPTION 
				"Poe table nodes group."
			::= { poeGroups 1 }

		
	
	END

--
-- DK-POE-MIB.my
--
